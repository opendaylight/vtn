/*
 * Copyright (c) 2015, 2016 NEC Corporation. All rights reserved.
 *
 * This program and the accompanying materials are made available under the
 * terms of the Eclipse Public License v1.0 which accompanies this distribution,
 * and is available at http://www.eclipse.org/legal/epl-v10.html
 */

module vtn-provider {
    yang-version 1;
    namespace "urn:opendaylight:vtn:impl:provider";
    prefix vtn-provider;

    /* OpenDaylight controller */
    import config {
        prefix config;
        revision-date 2013-04-05;
    }

    description
      "This module contains the base YANG definition for the VTN Manager
       provider implementation.";

    revision 2015-02-09 {
        description "Initial revision.";
    }

    identity vtn-provider {
        base config:module-type;

        // Specifies the prefix for generated Java classes.
        config:java-name-prefix VTNProvider;
    }

    // Augments the 'configuration' choice node under modules/module.
    augment "/config:modules/config:module/config:configuration" {
        case vtn-provider {
            when "/config:modules/config:module/config:type = 'vtn-provider'";
        }
    }
}
