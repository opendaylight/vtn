/*
 * Copyright (c) 2016 NEC Corporation. All rights reserved.
 *
 * This program and the accompanying materials are made available under the
 * terms of the Eclipse Public License v1.0 which accompanies this distribution,
 * and is available at http://www.eclipse.org/legal/epl-v10.html
 */

module vtn-neutron-config {
    yang-version 1;
    namespace "urn:opendaylight:vtn:neutron:config";
    prefix "vtn-neutron-config";

    description
        "The module that describes the configuration for VTN neutron service.";

    revision 2016-07-01 {
        description "Initial revision.";
    }

    container vtn-neutron-config {
        description "The configuration for VTN neutron service.";

        leaf bridge-name {
            description "Name of the bridge to create in OVS.";
            type string;
            default "br-int";
        }

        leaf port-name {
            description
                "Name of the interface to be added as port to the OVS bridge.";
            type string;
            default "eth1";
        }

        leaf protocol {
            description "OpenFlow Protocol 13 or 10.";
            type string;
            default "OpenFlow13";
        }

        leaf fail-mode {
            description "Failure mode.";
            type string;
            default "secure";
        }
    }
}
