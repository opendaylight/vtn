/*
 * Copyright (c) 2015 NEC Corporation
 * All rights reserved.
 *
 * This program and the accompanying materials are made available under the
 * terms of the Eclipse Public License v1.0 which accompanies this
 * distribution, and is available at http://www.eclipse.org/legal/epl-v10.html
 */

module ofmock-provider {
    yang-version 1;
    namespace "urn:opendaylight:vtn:it:ofmock:provider";
    prefix ofmock-provider;

    import config {
        prefix config;
        revision-date 2013-04-05;
    }
    import rpc-context {
        prefix rpcx;
        revision-date 2013-06-17;
    }
    import opendaylight-md-sal-binding {
        prefix mdsal;
        revision-date 2013-10-28;
    }
    import opendaylight-sal-binding-broker-impl {
        prefix broker;
        revision-date 2013-10-28;
    }

    description
      "This module contains the base YANG definition for the mock-up of
       openflowplugin provider implementation.";

    revision 2015-02-09 {
        description "Initial revision.";
    }

    identity ofmock-provider {
        base config:module-type;

        // Specifies the prefix for generated Java classes.
        config:java-name-prefix OfMockProvider;
    }

    // Augments the 'configuration' choice node under modules/module.
    augment "/config:modules/config:module/config:configuration" {
        case ofmock-provider {
            when
              "/config:modules/config:module/config:type = 'ofmock-provider'";

            container rpc-registry {
                uses config:service-ref {
                    refine type {
                        mandatory true;
                        config:required-identity mdsal:binding-rpc-registry;
                    }
                }
            }

            container notification-service {
                uses config:service-ref {
                    refine type {
                        mandatory true;
                        config:required-identity
                          broker:binding-new-notification-service;
                    }
                }
            }

            container notification-publish-service {
                uses config:service-ref {
                    refine type {
                        mandatory true;
                        config:required-identity
                          broker:binding-new-notification-publish-service;
                    }
                }
            }

            container data-broker {
                uses config:service-ref {
                    refine type {
                        mandatory true;
                        config:required-identity
                          mdsal:binding-async-data-broker;
                    }
                }
            }
        }
    }
}
