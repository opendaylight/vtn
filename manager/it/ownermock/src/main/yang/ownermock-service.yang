/*
 * Copyright (c) 2015 NEC Corporation
 * All rights reserved.
 *
 * This program and the accompanying materials are made available under the
 * terms of the Eclipse Public License v1.0 which accompanies this
 * distribution, and is available at http://www.eclipse.org/legal/epl-v10.html
 */

module ownermock-service {
    yang-version 1;
    namespace "urn:opendaylight:vtn:it:ownermock:service";
    prefix ownermock;

    /* OpenDaylight controller */
    import config {
        prefix config;
        revision-date 2013-04-05;
    }
    import opendaylight-entity-ownership-service {
        prefix ownership;
        revision-date 2015-08-10;
    }

    description
      "This module contains the base YANG definition for the mock-up of
       entity ownership service.";

    revision 2015-11-10 {
        description "Initial revision.";
    }

    identity ownermock-service {
        base config:module-type;
        config:provided-service ownership:entity-ownership-service;
        config:java-name-prefix OwnerMockService;
    }

    // Augments the 'configuration' choice node under modules/module.
    augment "/config:modules/config:module/config:configuration" {
        case ownermock-service {
            when
              "/config:modules/config:module/config:type = 'ownermock-service'";
        }
    }
}
