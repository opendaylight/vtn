/*
 * Copyright (c) 2015 NEC Corporation
 * All rights reserved.
 *
 * This program and the accompanying materials are made available under the
 * terms of the Eclipse Public License v1.0 which accompanies this
 * distribution, and is available at http://www.eclipse.org/legal/epl-v10.html
 */

module vtn-path-map {
    yang-version 1;
    namespace "urn:opendaylight:vtn:pathmap";
    prefix pathmap;

    import vtn-types {
        prefix vtype;
        revision-date 2015-02-09;
    }

    description
      "The module that describes the path map configuration.";

    revision 2015-03-28 {
        description "Initial revision.";
    }

    grouping vtn-path-map-config {
        description
          "Describes configuration for a path map.
           If `idle-timeout' field is configured, `hard-timeout' field also
           needs to be configured. If both `idle-timeout' and `hard-timeout'
           fields contain non-zero values, the value configured in
           `hard-timeout' needs to be greater than the value configured in
           `idle-timeout'.";

        uses vtype:vtn-index;

        leaf condition {
            description
              "The name of the flow condition that selects packets.
               This path map is invalidated if the flow condition specified
               by this field is not present.";
            type vtype:vnode-name;
            mandatory true;
        }

        leaf policy {
            description
              "The identifier of the path policy which determines the route
               of packets.
               This path map is invalidated if the path policy specified by
               this field is not present.
               Zero specifies the system default path policy which
               minimizes the number of hops in the packet route.
               If omitted, it will be treated as if zero is specified.";
            type int32 {
                range "0 .. 3";
            }
            default 0;
        }

        uses vtype:vtn-flow-timeout-config;
    }

    grouping vtn-path-map-list {
        description
          "A container that holds a list of path map configurations.";

        list vtn-path-map {
            description "A list of path maps.";
            key "index";
            uses vtn-path-map-config;
        }
    }

    container global-path-maps {
        description
          "The root container of all the global path map configurations.
           Global path maps affect flows in all VTNs, but the VTN path maps
           are always evaluated prior to the global path maps. Global path
           maps will be evaluated only if a packet does not match any VTN
           path map.
           Note that the path map configuration must be modified by RPC.
           Do not edit this container directly.";
        config false;
        presence "Indicates the path map management is active.";
        uses vtn-path-map-list;
    }

    /*
     * RPC definitions
     */

    grouping vtn-path-map-result {
        description
          "Describes a pair of path map index and `vtn-update-type'.

           This grouping is used as output of RPC that modifies the global or
           VTN path map configuration.";

        leaf index {
            description
              "The index value that specifies the flow match in the flow
               condition.";
            type int32;
        }

        uses vtype:vtn-rpc-result;
    }

    rpc set-path-map {
        description
          "Create or modify the global or VTN path map.

           This operation takes a list of `vtn-path-map-config', and
           put all configurations into the specified path map list.
           If the name of the VTN is specified, the given path maps are
           configured as the VTN path map. Otherwise they are configured as
           the global path map.

           Path map indices specified in the RPC input will be copied to the
           RPC output, and `status' field in `vtn-path-map-result' describes
           the result of the operation.

           `CREATED' indicates that the path map configuration specified by
           the index value has been newly created.

           `CHANGED' indicates that the path map configuration specified by
           the index value has been successfully changed.

           Null indicates that the path map configuration specified by the
           index value was not changed.

           On failure, one of vtn-error-tag value which indicates the cause
           of error is set into application tag in RPC error.

           `BADREQUEST' is set if the RPC input contains invalid data.

           `NOTFOUND' is set if the VTN specified by the name is not present.

           `INTERNALERROR' is set if the operation failed due to internal
           error.";
        input {
            leaf tenant-name {
                description
                  "The name of the VTN.
                   If this field is specified, the specified path map will
                   affect flows only in the specified VTN.
                   If this field is omitted, the specified path map will
                   affect flows in all the VTNs.";
                type string;
            }

            list path-map-list {
                description
                  "A list of `vtn-path-map-config' to be applied to the
                   path map configuration. Note that a duplicate match index
                   in this list will cause a `BADREQUEST' error.";
                uses vtn-path-map-config;
            }
        }

        output {
            list set-path-map-result {
                description
                  "Describes pairs of path map indices passed to the RPC input
                   and results.";
                uses vtn-path-map-result;
            }
        }
    }

    rpc remove-path-map {
        description
          "Remove the path map configuration in the global or VTN path map.

           Values passed to `map-index' list will be copied to the RPC
           output, and `status' field in `vtn-path-map-result' describes
           the result of the operation.

           `REMOVED' indicates that the path map associated with the map index
           has been successfully removed.

           Null indicates that the path map is not associated with the map
           index in the specified path map.

           On failure, one of vtn-error-tag value which indicates the cause
           of error is set into application tag in RPC error.

           `BADREQUEST' is set if the RPC input contains invalid data.

           `NOTFOUND' is set if the VTN specified by the name is not present.

           `INTERNALERROR' is set if the operation failed due to internal
           error.";
        input {
            leaf tenant-name {
                description
                  "The name of the VTN.
                   If this field is specified, path maps specified in the
                   RPC input will be removed from the VTN path map
                   configuration.
                   If this field is omitted, path maps specified in the
                   RPC input will be removed from the global path map
                   configuration.";
                type string;
            }

            leaf-list map-index {
                description
                  "A list of path map indices to be removed from the path map
                   configuration specified by `tenant-name' field.
                   Duplicates in this list will be eliminated automatically.";
                type int32;
            }
        }

        output {
            list remove-path-map-result {
                description
                  "Describes pairs of path map indices passed to the RPC input
                   and results.";
                uses vtn-path-map-result;
            }
        }
    }

    rpc clear-path-map {
        description
          "Remove all the path map configurations present in the global or
           VTN path map container.

           `status' in RPC output descripts the result of the operation.

           `REMOVED' indicates that at least one path map in the specified
           path map container has been removed.

           Null indicates that no configuration is present in the specified
           path map.

           On failure, one of vtn-error-tag value which indicates the cause
           of error is set into application tag in RPC error.

           `BADREQUEST' is set if the RPC input contains invalid data.

           `NOTFOUND' is set if the VTN specified by the name is not present.

           `INTERNALERROR' is set if the operation failed due to internal
           error.";
        input {
            leaf tenant-name {
                description
                  "The name of the VTN.
                   If this field is specified, all path map configurations
                   present in the specified VTN will be removed.
                   If this field is omitted, all global path map
                   configurations will be removed.";
                type string;
            }
        }

        output {
            uses vtype:vtn-rpc-result;
        }
    }
}
